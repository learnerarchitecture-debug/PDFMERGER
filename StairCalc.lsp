;;; Staircase Calculator for AutoCAD / ZWCAD
;;; Filename: StairCalc.lsp
;;; Version: 3.1 - Final

(vl-load-com)

(setq *stair:units-list* 
  '(("Millimeters (mm)" . 0) ("Centimeters (cm)" . 1) ("Meters (m)" . 2) 
    ("Inches (in)" . 3) ("Feet (ft)" . 4) ("Feet-Inches (ft-in)" . 5) ("Yards (yd)" . 6))
)
(setq *stair:dcl-fname* "")
(setq *stair:dcl-id* -1)
(setq *stair:result* nil)

(defun c:STAIRCALC ()
  (stair:ensure-dcl)
  (setq dcl-id (load_dialog *stair:dcl-fname*))
  (if (< dcl-id 0) (progn (princ "\nError: Could not load DCL file.") (exit)))
  (setq *stair:dcl-id* dcl-id)
  (if (not (new_dialog "staircalc" dcl-id))
    (progn (princ "\nError: Could not start dialog.") (unload_dialog dcl-id) (exit)))
  (stair:init-dialog)
  (stair:setup-callbacks)
  (start_dialog)
  (unload_dialog dcl-id)
  (princ)
)

(defun stair:ensure-dcl (/ f)
  (setq *stair:dcl-fname* (vl-filename-mktemp "staircalc" nil ".dcl"))
  (if (not (findfile *stair:dcl-fname*))
    (progn
      (setq f (open *stair:dcl-fname* "w"))
      (stair:write-dcl f)
      (close f)
    )
  )
)

(defun stair:write-dcl (f)
  (write-line "staircalc : dialog {" f)
  (write-line "  label = \"Staircase Calculator\";" f)
  (write-line "  : column {" f)
  (write-line "    : row {" f)
  (write-line "      : column {" f)
  (write-line "        : boxed_column {" f)
  (write-line "          label = \"Calculation Mode\";" f)
  (write-line "          : radio_column {" f)
  (write-line "            key = \"calc_mode\";" f)
  (write-line "            : radio_button { key = \"mode_ceil_slab\"; label = \"Ceiling + Slab -> Riser\"; }" f)
  (write-line "            : radio_button { key = \"mode_riser_steps\"; label = \"Riser + Ceiling -> #Steps\"; }" f)
  (write-line "            : radio_button { key = \"mode_steps_slab\"; label = \"#Steps + Slab -> Riser\"; }" f)
  (write-line "          }" f)
  (write-line "        }" f)
  (write-line "        : boxed_column {" f)
  (write-line "          label = \"Flight Shape\";" f)
  (write-line "          : popup_list { key = \"flight_type\"; width = 18; }" f)
  (write-line "        }" f)
  (write-line "      }" f)
  (write-line "      : column {" f)
  (write-line "        : boxed_column {" f)
  (write-line "          label = \"Inputs\";" f)
  (write-line "          : row {" f)
  (write-line "            : edit_box { key = \"ceiling_ht\"; label = \"Ceiling Ht\"; edit_width = 12; }" f)
  (write-line "            : popup_list { key = \"ceiling_unit\"; width = 14; }" f)
  (write-line "          }" f)
  (write-line "          : row {" f)
  (write-line "            : edit_box { key = \"slab_ht\"; label = \"Slab Thk\"; edit_width = 12; }" f)
  (write-line "            : popup_list { key = \"slab_unit\"; width = 14; }" f)
  (write-line "          }" f)
  (write-line "          : row {" f)
  (write-line "            : edit_box { key = \"riser_ht\"; label = \"Riser Ht\"; edit_width = 12; }" f)
  (write-line "            : popup_list { key = \"riser_unit\"; width = 14; }" f)
  (write-line "          }" f)
  (write-line "          : row {" f)
  (write-line "            : edit_box { key = \"tread_d\"; label = \"Tread D\"; edit_width = 12; }" f)
  (write-line "            : popup_list { key = \"tread_unit\"; width = 14; }" f)
  (write-line "          }" f)
  (write-line "          : row {" f)
  (write-line "            : edit_box { key = \"num_steps\"; label = \"# Steps\"; edit_width = 12; }" f)
  (write-line "          }" f)
  (write-line "          : row {" f)
  (write-line "            : edit_box { key = \"landing_d\"; label = \"Landing\"; edit_width = 12; }" f)
  (write-line "            : popup_list { key = \"landing_unit\"; width = 14; }" f)
  (write-line "          }" f)
  (write-line "        }" f)
  (write-line "      }" f)
  (write-line "    }" f)
  (write-line "    : boxed_column {" f)
  (write-line "      label = \"Results\";" f)
  (write-line "      : row {" f)
  (write-line "        : column {" f)
  (write-line "          : text { key = \"result_riser\"; label = \"Riser Height: \"; }" f)
  (write-line "          : text { key = \"result_tread\"; label = \"Tread Depth: \"; }" f)
  (write-line "          : text { key = \"result_ceiling\"; label = \"Ceiling Height: \"; }" f)
  (write-line "          : text { key = \"result_slab\"; label = \"Slab Thickness: \"; }" f)
  (write-line "          : text { key = \"result_risers\"; label = \"Number of Risers: \"; }" f)
  (write-line "          : text { key = \"result_treads\"; label = \"Number of Treads: \"; }" f)
  (write-line "          : text { key = \"result_total_run\"; label = \"Total Run: \"; }" f)
  (write-line "          : text { key = \"result_total_rise\"; label = \"Total Rise: \"; }" f)
  (write-line "        }" f)
  (write-line "        : column {" f)
  (write-line "          : text { key = \"result_comfort\"; label = \"Comfort: \"; }" f)
  (write-line "          : text { key = \"result_headroom\"; label = \"Headroom: \"; }" f)
  (write-line "          : text { key = \"result_stringer\"; label = \"Stringer Len: \"; }" f)
  (write-line "          : text { key = \"result_warning\"; label = \"Warning: \"; }" f)
  (write-line "          : text { key = \"result_flights\"; label = \"Flights: \"; }" f)
  (write-line "          : text { key = \"result_flight_run\"; label = \"Per Flight: \"; }" f)
  (write-line "        }" f)
  (write-line "      }" f)
  (write-line "      : text { key = \"result_unit\"; label = \"Display Unit: \"; }" f)
  (write-line "    }" f)
  (write-line "    : boxed_column {" f)
  (write-line "      label = \"Display Unit\";" f)
  (write-line "      : row {" f)
  (write-line "        : popup_list { key = \"disp_unit\"; width = 20; }" f)
  (write-line "        : toggle { key = \"auto_unit\"; label = \"Auto INSUNITS\"; value = \"1\"; }" f)
  (write-line "        : toggle { key = \"auto_notation\"; label = \"Auto ft/in\"; value = \"1\"; }" f)
  (write-line "      }" f)
  (write-line "    }" f)
  (write-line "    : row {" f)
  (write-line "      : button { key = \"draw_side\"; label = \"Draw Side\"; width = 10; }" f)
  (write-line "      : button { key = \"draw_plan\"; label = \"Draw Plan\"; width = 10; }" f)
  (write-line "      : button { key = \"export\"; label = \"Export\"; width = 10; }" f)
  (write-line "      : button { key = \"clear\"; label = \"Clear\"; width = 10; }" f)
  (write-line "      : button { key = \"cancel\"; label = \"Close\"; is_cancel = true; width = 10; }" f)
  (write-line "    }" f)
  (write-line "  }" f)
  (write-line "}" f)
)

(defun stair:init-dialog (/ units-list insunits-val idx flight-list)
  (setq units-list (mapcar 'car *stair:units-list*))
  (foreach key '("ceiling_unit" "slab_unit" "riser_unit" "tread_unit" "disp_unit" "landing_unit")
    (start_list key)
    (mapcar 'add_list units-list)
    (end_list)
    (set_tile key "0")
  )
  (setq flight-list '("Single Straight" "L-Shape" "U-Shape (Dog-Leg)" "Half Landing" "Quarter Turn"))
  (start_list "flight_type")
  (mapcar 'add_list flight-list)
  (end_list)
  (set_tile "flight_type" "0")
  (set_tile "slab_ht" "9") (set_tile "slab_unit" "3")
  (set_tile "landing_d" "48") (set_tile "landing_unit" "3")
  (setq insunits-val (getvar "INSUNITS"))
  (setq idx (stair:insunits-to-index insunits-val))
  (if idx (progn (set_tile "disp_unit" (itoa idx)) (set_tile "auto_unit" "1")))
  (set_tile "mode_ceil_slab" "1")
  (mode_ceil_slab_callback)
  (set_tile "auto_notation" "1")
)

(defun stair:setup-callbacks ()
  (action_tile "mode_ceil_slab" "(mode_ceil_slab_callback)")
  (action_tile "mode_riser_steps" "(mode_riser_steps_callback)")
  (action_tile "mode_steps_slab" "(mode_steps_slab_callback)")
  (action_tile "clear" "(stair:clear-fields)")
  (action_tile "cancel" "(done_dialog)")
  (action_tile "draw_side" "(done_dialog 1)")
  (action_tile "draw_plan" "(done_dialog 2)")
  (action_tile "export" "(done_dialog 3)")
  (foreach key '("ceiling_ht" "slab_ht" "riser_ht" "tread_d" "num_steps" "landing_d"
                 "ceiling_unit" "slab_unit" "riser_unit" "tread_unit" "landing_unit"
                 "auto_notation" "flight_type")
    (action_tile key "(stair:calculate)")
  )
)

(defun mode_ceil_slab_callback ()
  (mode_tile "ceiling_ht" 0) (mode_tile "ceiling_unit" 0)
  (mode_tile "slab_ht" 0) (mode_tile "slab_unit" 0)
  (mode_tile "riser_ht" 1) (mode_tile "riser_unit" 1)
  (mode_tile "tread_d" 0) (mode_tile "tread_unit" 0)
  (mode_tile "num_steps" 1)
  (set_tile "riser_ht" "") (set_tile "riser_unit" "3")
  (stair:calculate)
)

(defun mode_riser_steps_callback ()
  (mode_tile "ceiling_ht" 0) (mode_tile "ceiling_unit" 0)
  (mode_tile "slab_ht" 1) (mode_tile "slab_unit" 1)
  (mode_tile "riser_ht" 0) (mode_tile "riser_unit" 0)
  (mode_tile "tread_d" 1) (mode_tile "tread_unit" 1)
  (mode_tile "num_steps" 1)
  (set_tile "slab_ht" "0") (set_tile "slab_unit" "3")
  (set_tile "tread_d" "11") (set_tile "tread_unit" "3")
  (set_tile "num_steps" "")
  (stair:calculate)
)

(defun mode_steps_slab_callback ()
  (mode_tile "ceiling_ht" 0) (mode_tile "ceiling_unit" 0)
  (mode_tile "riser_ht" 1) (mode_tile "riser_unit" 1)
  (mode_tile "slab_ht" 0) (mode_tile "slab_unit" 0)
  (mode_tile "tread_d" 0) (mode_tile "tread_unit" 0)
  (mode_tile "num_steps" 0)
  (set_tile "riser_ht" "") (set_tile "riser_unit" "3")
  (set_tile "slab_ht" "9") (set_tile "slab_unit" "3")
  (stair:calculate)
)

(defun stair:insunits-to-index (ins)
  (cdr (assoc ins '((4 . 0) (5 . 1) (6 . 2) (1 . 3) (2 . 4))))
)

(defun stair:get-unit-idx (tile-key) (atoi (get_tile tile-key)))

(defun stair:parse-to-inches (str / val len i ch num feet inches in-ft in-in unit-suffix)
  (setq str (vl-string-trim " " (strcase str)))
  (if (= str "") (setq val 0.0)
    (progn
      (setq len (strlen str) i 0 val 0.0 num "" in-ft nil in-in nil unit-suffix "")
      (while (< i len)
        (setq ch (substr str (1+ i) 1))
        (cond
          ((or (= ch "'") (= ch "`") (= ch "\u00B4"))
           (if (and (not in-ft) num (> (strlen num) 0))
             (progn (setq feet (atof num) val (+ val (* feet 12.0)) num "" in-ft T))
           )
          )
           ((= ch "\"")
           (if (and (not in-in) num (> (strlen num) 0))
             (progn (setq inches (atof num) val (+ val inches) num "" in-in T))
           )
          )
          ((or (= ch " ") (= ch "-"))
           (if (and in-ft (not in-in) num (> (strlen num) 0))
             (progn (setq inches (atof num) val (+ val inches) num ""))
           )
          )
          ((wcmatch ch "[0-9.]") (setq num (strcat num ch)))
          (T (setq unit-suffix (strcat unit-suffix ch))
             (cond
               ((wcmatch unit-suffix "MM*") (if (> (strlen num) 0) (progn (setq val (+ val (/ (atof num) 25.4)) num "" unit-suffix ""))))
               ((wcmatch unit-suffix "CM*") (if (> (strlen num) 0) (progn (setq val (+ val (/ (atof num) 2.54)) num "" unit-suffix ""))))
               ((wcmatch unit-suffix "YD*") (if (> (strlen num) 0) (progn (setq val (+ val (* (atof num) 36.0)) num "" unit-suffix ""))))
               ((wcmatch unit-suffix "FT*") (if (> (strlen num) 0) (progn (setq val (+ val (* (atof num) 12.0)) num "" unit-suffix ""))))
               ((wcmatch unit-suffix "IN*") (if (> (strlen num) 0) (progn (setq val (+ val (atof num)) num "" unit-suffix ""))))
             )
          )
        )
        (setq i (1+ i))
      )
      (if (and num (> (strlen num) 0) (= val 0.0)) (setq val (atof num)))
    )
  )
  val
)

(defun stair:convert-to-inches (val unit-idx)
  (cond
    ((= unit-idx 0) (/ val 25.4)) ((= unit-idx 1) (/ val 2.54))
    ((= unit-idx 2) (/ val 0.0254)) ((= unit-idx 3) val)
    ((= unit-idx 4) (* val 12.0)) ((= unit-idx 5) val)
    ((= unit-idx 6) (* val 36.0)) (T val)))

(defun stair:inches-to-unit (val unit-idx)
  (cond
    ((= unit-idx 0) (* val 25.4)) ((= unit-idx 1) (* val 2.54))
    ((= unit-idx 2) (* val 0.0254)) ((= unit-idx 3) val)
    ((= unit-idx 4) (/ val 12.0)) ((= unit-idx 5) val)
    ((= unit-idx 6) (/ val 36.0)) (T val)))

(defun stair:format-value (val-inches unit-idx / ft in)
  (cond
    ((= unit-idx 0) (strcat (rtos val-inches 2 1) " mm"))
    ((= unit-idx 1) (strcat (rtos val-inches 2 2) " cm"))
    ((= unit-idx 2) (strcat (rtos val-inches 2 3) " m"))
    ((= unit-idx 3) (strcat (rtos val-inches 2 2) "\""))
    ((= unit-idx 4) (strcat (rtos (/ val-inches 12.0) 2 3) " ft"))
    ((= unit-idx 5) (setq ft (fix (/ val-inches 12.0)) in (- val-inches (* ft 12.0))) (strcat (itoa ft) "' " (rtos in 2 2) "\""))
    ((= unit-idx 6) (strcat (rtos (/ val-inches 36.0) 2 3) " yd"))
    (T (rtos val-inches 2 2))))

(defun stair:get-input-inches (edit-key unit-key / str unit-idx val)
  (setq str (get_tile edit-key))
  (if (= (vl-string-trim " " str) "") (setq val 0.0)
    (progn
      (setq unit-idx (stair:get-unit-idx unit-key))
      (if (= (get_tile "auto_notation") "1") (setq val (stair:parse-to-inches str))
        (setq val (stair:convert-to-inches (atof str) unit-idx)))
    )
  )
  val
)

(defun stair:calculate (/ mode ceiling-ht-in slab-ht-in riser-ht-in tread-d-in disp-idx num-steps landing-d flight-type
                          total-rise risers treads total-run comfort headroom stringer-len warning
                          flight-count per-flight-run)
  (setq mode (cond
    ((= (get_tile "mode_ceil_slab") "1") "ceil_slab")
    ((= (get_tile "mode_riser_steps") "1") "riser_steps")
    ((= (get_tile "mode_steps_slab") "1") "steps_slab")
    (T "ceil_slab")))
  (setq disp-idx (stair:get-unit-idx "disp_unit")
        flight-type (atoi (get_tile "flight_type"))
        landing-d (stair:get-input-inches "landing_d" "landing_unit"))
  (if (< landing-d 0) (setq landing-d 0))
  
  (cond
    ;; MODE 1: Ceiling + Slab -> Riser (auto-optimal)
    ((= mode "ceil_slab")
     (progn
       (setq ceiling-ht-in (stair:get-input-inches "ceiling_ht" "ceiling_unit")
             slab-ht-in (stair:get-input-inches "slab_ht" "slab_unit")
             total-rise (+ ceiling-ht-in slab-ht-in))
       (if (> total-rise 0.0)
         (progn
           (setq risers (fix (/ total-rise 7.0)))
           (if (< risers 1) (setq risers 1))
           (setq riser-ht-in (/ total-rise risers))
           (if (or (< riser-ht-in 5.0) (> riser-ht-in 8.5))
             (progn (setq risers2 (1+ risers)) (setq riser2 (/ total-rise risers2))
                    (if (and (>= riser2 5.0) (<= riser2 8.5)) (progn (setq risers risers2) (setq riser-ht-in riser2)))))
           (setq treads (1- risers)
                 tread-d-in (stair:get-input-inches "tread_d" "tread_unit"))
           (if (= tread-d-in 0.0) (setq tread-d-in (- 25.0 (* 2.0 riser-ht-in))))
           (if (< tread-d-in 9.0) (setq tread-d-in 9.0))
           (if (> tread-d-in 14.0) (setq tread-d-in 14.0))
           (setq total-run (* treads tread-d-in))
           (setq flight-count 1)
           (cond ((= flight-type 1) (setq flight-count 2)) ((= flight-type 2) (setq flight-count 2))
                 ((= flight-type 3) (setq flight-count 2)) ((= flight-type 4) (setq flight-count 2)))
           (setq per-flight-run (/ total-run flight-count)
                 comfort (+ (* 2.0 riser-ht-in) tread-d-in)
                 headroom (- total-rise (* 0.5 tread-d-in))
                 stringer-len (sqrt (+ (* total-run total-run) (* total-rise total-rise)))
                 warning "")
           (if (< headroom 80.0) (setq warning (strcat warning "HEADROOM < 6'8\"! ")))
           (if (> total-run 144.0) (setq warning (strcat warning "RUN > 12ft! ")))
           (if (or (< comfort 24.0) (> comfort 25.0)) (setq warning (strcat warning "2R+T outside 24-25\" ")))
           (setq *stair:result* (list riser-ht-in tread-d-in ceiling-ht-in slab-ht-in
                                      risers treads total-run total-rise
                                      comfort headroom stringer-len warning flight-count per-flight-run landing-d))
           (stair:update-results disp-idx))
         (stair:clear-results))))
    ;; MODE 2: Riser + Ceiling -> #Steps
    ((= mode "riser_steps")
     (progn
       (setq riser-ht-in (stair:get-input-inches "riser_ht" "riser_unit")
             ceiling-ht-in (stair:get-input-inches "ceiling_ht" "ceiling_unit")
             slab-ht-in 0.0
             total-rise ceiling-ht-in)
       (if (and (> riser-ht-in 0.0) (> total-rise 0.0))
         (progn
           (setq risers (max 1 (fix (/ total-rise riser-ht-in))))
           (set_tile "num_steps" (itoa risers))
           (setq treads (1- risers)
                 tread-d-in 11.0
                 total-run (* treads tread-d-in))
           (setq flight-count 1)
           (cond ((= flight-type 1) (setq flight-count 2)) ((= flight-type 2) (setq flight-count 2))
                 ((= flight-type 3) (setq flight-count 2)) ((= flight-type 4) (setq flight-count 2)))
           (setq per-flight-run (/ total-run flight-count)
                 comfort (+ (* 2.0 riser-ht-in) tread-d-in)
                 headroom (- total-rise (* 0.5 tread-d-in))
                 stringer-len (sqrt (+ (* total-run total-run) (* total-rise total-rise)))
                 warning "")
           (if (< headroom 80.0) (setq warning (strcat warning "HEADROOM < 6'8\"! ")))
           (if (> total-run 144.0) (setq warning (strcat warning "RUN > 12ft! ")))
           (if (or (< comfort 24.0) (> comfort 25.0)) (setq warning (strcat warning "2R+T outside 24-25\" ")))
           (setq *stair:result* (list riser-ht-in tread-d-in ceiling-ht-in slab-ht-in
                                      risers treads total-run total-rise
                                      comfort headroom stringer-len warning flight-count per-flight-run landing-d))
           (stair:update-results disp-idx))
         (stair:clear-results))))
    ;; MODE 3: #Steps + Slab -> Riser
    ((= mode "steps_slab")
     (progn
       (setq ceiling-ht-in (stair:get-input-inches "ceiling_ht" "ceiling_unit")
             slab-ht-in (stair:get-input-inches "slab_ht" "slab_unit")
             total-rise (+ ceiling-ht-in slab-ht-in)
             num-steps (atoi (get_tile "num_steps")))
       (if (and (> total-rise 0.0) (> num-steps 0))
         (progn
           (setq risers num-steps riser-ht-in (/ total-rise risers)
                 treads (1- risers)
                 tread-d-in (stair:get-input-inches "tread_d" "tread_unit"))
           (if (= tread-d-in 0.0) (setq tread-d-in (- 25.0 (* 2.0 riser-ht-in))))
           (if (< tread-d-in 9.0) (setq tread-d-in 9.0))
           (if (> tread-d-in 14.0) (setq tread-d-in 14.0))
           (setq total-run (* treads tread-d-in))
           (setq flight-count 1)
           (cond ((= flight-type 1) (setq flight-count 2)) ((= flight-type 2) (setq flight-count 2))
                 ((= flight-type 3) (setq flight-count 2)) ((= flight-type 4) (setq flight-count 2)))
           (setq per-flight-run (/ total-run flight-count)
                 comfort (+ (* 2.0 riser-ht-in) tread-d-in)
                 headroom (- total-rise (* 0.5 tread-d-in))
                 stringer-len (sqrt (+ (* total-run total-run) (* total-rise total-rise)))
                 warning "")
           (if (< headroom 80.0) (setq warning (strcat warning "HEADROOM < 6'8\"! ")))
           (if (> total-run 144.0) (setq warning (strcat warning "RUN > 12ft! ")))
           (if (or (< comfort 24.0) (> comfort 25.0)) (setq warning (strcat warning "2R+T outside 24-25\" ")))
           (setq *stair:result* (list riser-ht-in tread-d-in ceiling-ht-in slab-ht-in
                                      risers treads total-run total-rise
                                      comfort headroom stringer-len warning flight-count per-flight-run landing-d))
           (stair:update-results disp-idx))
         (stair:clear-results)))))
  (princ)
)

(defun stair:update-results (disp-idx / r)
  (setq r *stair:result*)
  (set_tile "result_riser" (strcat "Riser Height: " (stair:format-value (nth 0 r) disp-idx)))
  (set_tile "result_tread" (strcat "Tread Depth: " (stair:format-value (nth 1 r) disp-idx)))
  (set_tile "result_ceiling" (strcat "Ceiling Height: " (stair:format-value (nth 2 r) disp-idx)))
  (set_tile "result_slab" (strcat "Slab Thickness: " (stair:format-value (nth 3 r) disp-idx)))
  (set_tile "result_risers" (strcat "Number of Risers: " (itoa (nth 4 r))))
  (set_tile "result_treads" (strcat "Number of Treads: " (itoa (nth 5 r))))
  (set_tile "result_total_run" (strcat "Total Run: " (stair:format-value (nth 6 r) disp-idx)))
  (set_tile "result_total_rise" (strcat "Total Rise: " (stair:format-value (nth 7 r) disp-idx)))
  (if (and (>= (nth 8 r) 24.0) (<= (nth 8 r) 25.0))
    (set_tile "result_comfort" (strcat "Comfort: " (rtos (nth 8 r) 2 1) "\" (IDEAL)"))
    (set_tile "result_comfort" (strcat "Comfort: " (rtos (nth 8 r) 2 1) "\" (2R+T=24-25\")")))
  (if (>= (nth 9 r) 80.0)
    (set_tile "result_headroom" (strcat "Headroom: " (stair:format-value (nth 9 r) disp-idx) " OK"))
    (set_tile "result_headroom" (strcat "Headroom: " (stair:format-value (nth 9 r) disp-idx) " LOW!")))
  (set_tile "result_stringer" (strcat "Stringer Len: " (stair:format-value (nth 10 r) disp-idx)))
  (if (= (nth 11 r) "") (set_tile "result_warning" "Warning: NONE")
    (set_tile "result_warning" (strcat "Warning: " (nth 11 r))))
  (set_tile "result_flights" (strcat "Flights: " (itoa (nth 12 r))))
  (set_tile "result_flight_run" (strcat "Per Flight: " (stair:format-value (nth 13 r) disp-idx)))
  (set_tile "result_unit" (strcat "Display Unit: " (car (nth disp-idx *stair:units-list*))))
)

(defun stair:clear-results ()
  (foreach key '("result_riser" "result_tread" "result_ceiling" "result_slab"
                 "result_risers" "result_treads" "result_total_run" "result_total_rise"
                 "result_comfort" "result_headroom" "result_stringer" "result_warning"
                 "result_flights" "result_flight_run" "result_unit")
    (set_tile key "")))

(defun stair:clear-fields ()
  (foreach key '("ceiling_ht" "slab_ht" "riser_ht" "tread_d" "num_steps" "landing_d"
                 "result_riser" "result_tread" "result_ceiling" "result_slab"
                 "result_risers" "result_treads" "result_total_run" "result_total_rise"
                 "result_comfort" "result_headroom" "result_stringer" "result_warning"
                 "result_flights" "result_flight_run" "result_unit")
    (set_tile key ""))
  (set_tile "slab_ht" "9") (set_tile "slab_unit" "3")
  (set_tile "landing_d" "48") (set_tile "landing_unit" "3")
  (set_tile "mode_ceil_slab" "1") (set_tile "flight_type" "0")
  (mode_ceil_slab_callback)
  (princ))

(defun stair:toggle-auto-unit ()
  (if (= (get_tile "auto_unit") "1")
    (progn (setq idx (stair:insunits-to-index (getvar "INSUNITS")))
           (if idx (set_tile "disp_unit" (itoa idx)))))
  (stair:calculate))

(defun c:STAIRCALC-DRAW (/ pt riser-ht-in total-run total-rise risers treads old-layer old-osmode layer-name i pt1 pt2 pt3)
  (if (not *stair:result*) (progn (princ "\nRun STAIRCALC first.") (exit)))
  (setq riser-ht-in (nth 0 *stair:result*) total-run (nth 6 *stair:result*)
        total-rise (nth 7 *stair:result*) risers (nth 4 *stair:result*) treads (nth 5 *stair:result*))
  (setq pt (getpoint "\nPick stair start point: "))
  (if (not pt) (exit))
  (setq layer-name "STAIR_CALC")
  (if (not (tblsearch "LAYER" layer-name))
    (command "._LAYER" "_M" layer-name "_C" "3" "" "_L" "CONTINUOUS" "" ""))
  (setq old-layer (getvar "CLAYER") old-osmode (getvar "OSMODE"))
  (setvar "CLAYER" layer-name) (setvar "OSMODE" 0)
  (command "._PLINE" pt (list (+ (car pt) total-run) (cadr pt))
           (list (+ (car pt) total-run) (+ (cadr pt) total-rise))
           (list (car pt) (+ (cadr pt) total-rise)) "_C")
  (setq i 0)
  (while (< i risers)
    (setq pt1 (list (+ (car pt) (* i 11.0)) (+ (cadr pt) (* i riser-ht-in)))
          pt2 (list (+ (car pt) (* (1+ i) 11.0)) (+ (cadr pt) (* i riser-ht-in)))
          pt3 (list (+ (car pt) (* i 11.0)) (+ (cadr pt) (* (1+ i) riser-ht-in))))
    (command "._LINE" pt1 pt2 "") (command "._LINE" pt1 pt3 "")
    (setq i (1+ i)))
  (command "._DIMLINEAR" pt (list (+ (car pt) total-run) (cadr pt))
           (polar (list (/ (+ (car pt) (+ (car pt) total-run)) 2.0) (cadr pt)) (* pi 1.5) 30.0))
  (command "._DIMLINEAR" pt (list (car pt) (+ (cadr pt) total-rise))
           (polar (list (car pt) (/ (+ (cadr pt) (+ (cadr pt) total-rise)) 2.0)) pi 30.0))
  (setvar "CLAYER" old-layer) (setvar "OSMODE" old-osmode)
  (command "._ZOOM" "_E")
  (princ "\nSide elevation drawn."))

(defun c:STAIRCALC-PLAN (/ pt treads total-run risers riser-ht-in old-layer old-osmode layer-name i pt1 pt2)
  (if (not *stair:result*) (progn (princ "\nRun STAIRCALC first.") (exit)))
  (setq treads (nth 5 *stair:result*) total-run (nth 6 *stair:result*)
        risers (nth 4 *stair:result*) riser-ht-in (nth 0 *stair:result*))
  (setq pt (getpoint "\nPick plan view start: "))
  (if (not pt) (exit))
  (setq layer-name "STAIR_CALC")
  (if (not (tblsearch "LAYER" layer-name))
    (command "._LAYER" "_M" layer-name "_C" "3" "" "_L" "CONTINUOUS" "" ""))
  (setq old-layer (getvar "CLAYER") old-osmode (getvar "OSMODE"))
  (setvar "CLAYER" layer-name) (setvar "OSMODE" 0)
  (command "._PLINE" pt (list (+ (car pt) total-run) (cadr pt))
           (list (+ (car pt) total-run) (+ (cadr pt) 48.0))
           (list (car pt) (+ (cadr pt) 48.0)) "_C")
  (setq i 0)
  (while (< i treads)
    (setq pt1 (list (+ (car pt) (* (1+ i) 11.0)) (cadr pt))
          pt2 (list (+ (car pt) (* (1+ i) 11.0)) (+ (cadr pt) 48.0)))
    (command "._LINE" pt1 pt2 "")
    (command "._TEXT" (list (+ (car pt) (* i 11.0) 5.5) (+ (cadr pt) 24.0)) 8.0 0 (itoa (+ i 1)))
    (setq i (1+ i)))
  (command "._DIMLINEAR" pt (list (+ (car pt) total-run) (cadr pt))
           (polar (list (/ (+ (car pt) (+ (car pt) total-run)) 2.0) (cadr pt)) (* pi 1.5) 24.0))
  (setvar "CLAYER" old-layer) (setvar "OSMODE" old-osmode)
  (command "._ZOOM" "_E")
  (princ "\nPlan view drawn."))

(defun c:STAIRCALC-EXPORT (/ fp fname r disp-idx)
  (if (not *stair:result*) (progn (princ "\nRun STAIRCALC first.") (exit)))
  (setq r *stair:result* disp-idx (atoi (get_tile "disp_unit")))
  (setq fname (getfiled "Save Report" "" "txt" 1))
  (if fname
    (progn
      (setq fp (open fname "w"))
      (write-line "========================================" fp)
      (write-line "  STAIRCASE CALCULATOR REPORT" fp)
      (write-line "========================================" fp)
      (write-line "" fp)
      (write-line (strcat "Riser Height:     " (stair:format-value (nth 0 r) disp-idx)) fp)
      (write-line (strcat "Tread Depth:      " (stair:format-value (nth 1 r) disp-idx)) fp)
      (write-line (strcat "Ceiling Height:   " (stair:format-value (nth 2 r) disp-idx)) fp)
      (write-line (strcat "Slab Thickness:   " (stair:format-value (nth 3 r) disp-idx)) fp)
      (write-line "" fp)
      (write-line (strcat "Number of Risers: " (itoa (nth 4 r))) fp)
      (write-line (strcat "Number of Treads: " (itoa (nth 5 r))) fp)
      (write-line (strcat "Total Run:        " (stair:format-value (nth 6 r) disp-idx)) fp)
      (write-line (strcat "Total Rise:       " (stair:format-value (nth 7 r) disp-idx)) fp)
      (write-line "" fp)
      (write-line "----------------------------------------" fp)
      (write-line (strcat "Comfort (2R+T):   " (rtos (nth 8 r) 2 1) "\"") fp)
      (write-line (strcat "Headroom:         " (stair:format-value (nth 9 r) disp-idx)) fp)
      (write-line (strcat "Stringer Length:  " (stair:format-value (nth 10 r) disp-idx)) fp)
      (write-line (strcat "Flights:          " (itoa (nth 12 r))) fp)
      (write-line (strcat "Per Flight Run:   " (stair:format-value (nth 13 r) disp-idx)) fp)
      (write-line "" fp)
      (write-line (strcat "Warning:          " (nth 11 r)) fp)
      (write-line "========================================" fp)
      (close fp)
      (princ (strcat "\nReport saved to: " fname))))
  (princ))

(defun c:STAIRCALC-HELP ()
  (princ "\n========================================")
  (princ "\n  Staircase Calculator v3.1")
  (princ "\n========================================")
  (princ "\n")
  (princ "\nCOMMANDS:")
  (princ "\n  STAIRCALC       - Open calculator")
  (princ "\n  STAIRCALC-DRAW  - Draw side elevation")
  (princ "\n  STAIRCALC-PLAN  - Draw plan view")
  (princ "\n  STAIRCALC-EXPORT - Export report to .txt")
  (princ "\n  STAIRCALC-HELP  - Show this help")
  (princ "\n")
  (princ "\nMODES:")
  (princ "\n  1. Ceiling + Slab -> Riser (auto-optimal)")
  (princ "\n  2. Riser + Ceiling -> #Steps")
  (princ "\n  3. #Steps + Slab -> Riser")
  (princ "\n")
  (princ "\nCHECKS:")
  (princ "\n  - Comfort: 2R+T = 24-25in (ideal)")
  (princ "\n  - Headroom: min 6ft 8in (80in)")
  (princ "\n  - Total run warning: > 12ft single flight")
  (princ "\n")
  (princ "\nUNITS: mm, cm, m, in, ft, ft-in, yd (auto-detect)")
  (princ "\n========================================")
  (princ))

(princ "\nStairCalc.lsp v3.1 loaded.")
(princ "\nCommands: STAIRCALC | STAIRCALC-DRAW | STAIRCALC-PLAN | STAIRCALC-EXPORT")
(princ "\nType STAIRCALC-HELP for help.")
(princ)
